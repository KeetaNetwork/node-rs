KYCAttributes DEFINITIONS ::= BEGIN

    KYCAttributes ::= SEQUENCE OF Attribute

    Attribute ::= SEQUENCE {
        -- Name of the attribute
        name        OBJECT IDENTIFIER,
        -- Value of this attribute
        value       CHOICE {
            -- A plain value, not sensitive
            plainValue       [0] IMPLICIT OCTET STRING,
            -- A sensitive value, encoded as a SensitiveAttribute in DER encoding
            sensitiveValue   [1] IMPLICIT OCTET STRING
        }
    }

END
