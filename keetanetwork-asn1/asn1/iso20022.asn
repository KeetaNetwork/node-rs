Iso20022 DEFINITIONS EXPLICIT TAGS ::= BEGIN

    Country ::= UTF8String --1.3.6.1.4.1.62675.1.2.0
    CountrySubDivision ::= UTF8String --1.3.6.1.4.1.62675.1.2.1
    PostalCode ::= UTF8String --1.3.6.1.4.1.62675.1.2.3
    TownName ::= UTF8String --1.3.6.1.4.1.62675.1.2.4
    BuildingNumber ::= UTF8String --1.3.6.1.4.1.62675.1.2.5
    StreetName ::= UTF8String --1.3.6.1.4.1.62675.1.2.6
    AddressLines ::= SEQUENCE OF UTF8String --1.3.6.1.4.1.62675.1.2.7
    SubDepartment ::= UTF8String --1.3.6.1.4.1.62675.1.2.8
    Department ::= UTF8String --1.3.6.1.4.1.62675.1.2.9
    EmailAddressPurpose ::= UTF8String --1.3.6.1.4.1.62675.1.3.0
    FullName ::= UTF8String --1.3.6.1.4.1.62675.1.0
    FirstName ::= UTF8String --1.3.6.1.4.1.62675.1.0.1
    LastName ::= UTF8String --1.3.6.1.4.1.62675.1.0.2
    MiddleName ::= UTF8String --1.3.6.1.4.1.62675.1.0.3
    BirthDate ::= GeneralizedTime --1.3.6.1.4.1.62675.1.1
    EmailAddress ::= UTF8String --1.3.6.1.4.1.62675.1.3
    PhoneNumber ::= UTF8String --1.3.6.1.4.1.62675.1.4
    JobTitle ::= UTF8String --1.3.6.1.4.1.62675.1.6
    JobResponsibility ::= UTF8String --1.3.6.1.4.1.62675.1.6.1
    Id ::= UTF8String     --1.3.6.1.4.1.62675.1.7
    Issuer ::= UTF8String --1.3.6.1.4.1.62675.1.7.1
    Nationality ::= UTF8String --1.3.6.1.4.1.62675.1.10

    AddressType ::= CHOICE { -- 1.3.6.1.4.1.62675.1.2.10
        code              [0] EXPLICIT UTF8String,
        proprietary       [1] EXPLICIT UTF8String
    }

    OrganizationIdentificationSchemeNameChoice ::= CHOICE { -- 1.3.6.1.4.1.62675.1.8.0.2
        code              [0] EXPLICIT UTF8String,
        proprietary       [1] EXPLICIT UTF8String
    }

    PersonIdentificationSchemeNameChoice ::= CHOICE { -- 1.3.6.1.4.1.62675.1.8.1.1
        code              [0] EXPLICIT UTF8String,
        proprietary       [1] EXPLICIT PersonIdentificationSchemeNameProprietary
    }

    DigestInfo ::= SEQUENCE {
        digestAlgorithm   OBJECT IDENTIFIER,
        digest            OCTET STRING
    }

    ExternalReference ::= SEQUENCE {
        url               UTF8String,
        contentType       UTF8String
    }

    Reference ::= SEQUENCE {
        external          ExternalReference,
        digest            DigestInfo,
        encryptionAlgorithm OBJECT IDENTIFIER
    }

    Address ::= SEQUENCE { --1.3.6.1.4.1.62675.1.2
        addressLines      [0] EXPLICIT AddressLines OPTIONAL,
        addressType       [1] EXPLICIT AddressType OPTIONAL,
        buildingNumber    [2] EXPLICIT BuildingNumber OPTIONAL,
        country           [3] EXPLICIT Country OPTIONAL,
        countrySubDivision [4] EXPLICIT CountrySubDivision OPTIONAL,
        department        [5] EXPLICIT Department OPTIONAL,
        postalCode        [6] EXPLICIT PostalCode OPTIONAL,
        streetName        [7] EXPLICIT StreetName OPTIONAL,
        subDepartment     [8] EXPLICIT SubDepartment OPTIONAL,
        townName          [9] EXPLICIT TownName OPTIONAL
    }

    DateAndPlaceOfBirth ::= SEQUENCE { --1.3.6.1.4.1.62675.1.5
        birthDate         [0] EXPLICIT BirthDate,
        cityOfBirth       [1] EXPLICIT TownName,
        countryOfBirth    [2] EXPLICIT Country,
        provinceOfBirth   [3] EXPLICIT CountrySubDivision OPTIONAL
    }

    EntityType ::= SEQUENCE { --1.3.6.1.4.1.62675.1.8
        organization      [0] EXPLICIT SEQUENCE OF GenericOrganizationIdentification OPTIONAL,
        person            [1] EXPLICIT SEQUENCE OF GenericPersonIdentification OPTIONAL
    }

    ContactDetails ::= SEQUENCE { --1.3.6.1.4.1.62675.1.9
        department        [0] EXPLICIT Department OPTIONAL,
        emailAddress      [1] EXPLICIT EmailAddress OPTIONAL,
        emailPurpose      [2] EXPLICIT EmailAddressPurpose OPTIONAL,
        faxNumber         [3] EXPLICIT PhoneNumber OPTIONAL,
        fullName          [4] EXPLICIT FullName OPTIONAL,
        jobResponsibility [5] EXPLICIT JobResponsibility OPTIONAL,
        jobTitle          [6] EXPLICIT JobTitle OPTIONAL,
        mobileNumber      [7] EXPLICIT PhoneNumber OPTIONAL,
        namePrefix        [8] EXPLICIT NamePrefixCode OPTIONAL,
        other             [9] EXPLICIT SEQUENCE OF OtherContact OPTIONAL,
        phoneNumber       [10] EXPLICIT PhoneNumber OPTIONAL,
        preferredMethod   [11] EXPLICIT PreferredContactMethodCode OPTIONAL
    }

    Document ::= SEQUENCE { --1.3.6.1.4.1.62675.1.11
        documentNumber    [0] EXPLICIT UTF8String,
        front             [1] EXPLICIT Reference OPTIONAL,
        back              [2] EXPLICIT Reference OPTIONAL,
        selfie            [3] EXPLICIT Reference OPTIONAL,
        fullName          [4] EXPLICIT UTF8String OPTIONAL,
        firstName         [5] EXPLICIT UTF8String OPTIONAL,
        lastName          [6] EXPLICIT UTF8String OPTIONAL,
        dob               [7] EXPLICIT GeneralizedTime OPTIONAL,
        gender            [8] EXPLICIT UTF8String OPTIONAL,
        address           [9] EXPLICIT Address OPTIONAL,
        expiresAt         [10] EXPLICIT GeneralizedTime OPTIONAL,
        issuedAt          [11] EXPLICIT GeneralizedTime OPTIONAL,
        issuingState      [12] EXPLICIT UTF8String OPTIONAL,
        issuingCountry    [13] EXPLICIT UTF8String OPTIONAL,
        refNumber         [14] EXPLICIT UTF8String OPTIONAL,
        nationality       [15] EXPLICIT UTF8String OPTIONAL,
        curp              [16] EXPLICIT UTF8String OPTIONAL,
        claveDeElector    [17] EXPLICIT UTF8String OPTIONAL,
        classifiedDocumentType [18] EXPLICIT UTF8String OPTIONAL,
        curpValidationResponse [19] EXPLICIT UTF8String OPTIONAL,
        sambaActivityHistoryResponse [20] EXPLICIT UTF8String OPTIONAL
    }

    -- OrganizationIdentification (1.3.6.1.4.1.62675.1.8.0): SEQUENCE OF CHOICE
    OrganizationIdentificationChoice ::= CHOICE {
        bic               [0] EXPLICIT UTF8String,
        lei               [1] EXPLICIT UTF8String,
        other             [2] EXPLICIT SEQUENCE OF GenericOrganizationIdentification
    }

    OrganizationIdentification ::= SEQUENCE OF OrganizationIdentificationChoice

    GenericOrganizationIdentification ::= SEQUENCE { --1.3.6.1.4.1.62675.1.8.0.1
        id                [0] EXPLICIT Id,
        issuer            [1] EXPLICIT Issuer OPTIONAL,
        schemeName        [2] EXPLICIT OrganizationIdentificationSchemeNameChoice OPTIONAL
    }

    -- PersonIdentification (1.3.6.1.4.1.62675.1.8.1): SEQUENCE OF CHOICE
    PersonIdentificationChoice ::= CHOICE {
        dateAndPlaceOfBirth [0] EXPLICIT DateAndPlaceOfBirth,
        other             [1] EXPLICIT SEQUENCE OF GenericPersonIdentification
    }

    PersonIdentification ::= SEQUENCE OF PersonIdentificationChoice

    GenericPersonIdentification ::= SEQUENCE { --1.3.6.1.4.1.62675.1.8.1.0
        id                [0] EXPLICIT Id,
        issuer            [1] EXPLICIT Issuer OPTIONAL,
        schemeName        [2] EXPLICIT PersonIdentificationSchemeNameChoice OPTIONAL
    }

    OtherContact ::= SEQUENCE { --1.3.6.1.4.1.62675.1.9.1
        channelType       [0] EXPLICIT UTF8String,
        id                [1] EXPLICIT Id OPTIONAL
    }

    NamePrefixCode ::= ENUMERATED { --1.3.6.1.4.1.62675.1.0.0
        DOCT, MIST, MISS, MIKS, MME
    }

    PersonIdentificationSchemeNameProprietary ::= ENUMERATED { --1.3.6.1.4.1.62675.1.8.1.1.0
        DRLC, CPPT, ARNU, SSN, TXID, VISA, WPPT
    }

    PreferredContactMethodCode ::= ENUMERATED { --1.3.6.1.4.1.62675.1.9.0
        LETT, MAIL, PHON, FAXX, CELL
    }

END
