AlgorithmIdentifierDefinitions DEFINITIONS ::= BEGIN

    AlgorithmIdentifier ::= SEQUENCE {
        algorithm               OBJECT IDENTIFIER,
        parameters              ANY OPTIONAL
    }

END
